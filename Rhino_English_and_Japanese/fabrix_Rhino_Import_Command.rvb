' 3D-G-CODE SCRIPT

'///////////////////////////////////////////////////////////////////////////////////////////////////////////////////////////////////////////////////////////////////////////////////////////////
'//
'//
'// Fabrix Script
'// G-CODE-IMPORT PLUGIN for Rhino
'// (c) Hiroya Tanaka, Social Fabrication Lab, Keio University, Japan, 2016 - 2017
'// 
'// Project Official Website:  http://www.fabrix.design/ 
'// 
'// 
'///////////////////////////////////////////////////////////////////////////////////////////////////////////////////////////////////////////////////////////////////////////////////////////////

' Script Reference: caducopia
' http://caducopia.com/wordpress/?page_id=12
' Thank you very much !!! 


Option Explicit
call main ' exec on load

Sub main
Dim FabrixFSO, oFile, FileName, strLine, strLines
Dim arrItems(6), arrValues(6), strMessage, strTitle, strProperties
Dim arrRhinoUnits(10), strUnitsError
Dim intLineCount, intLineTotal
Dim L, i, X, Y, Z, arrXYZ(), G, M, Eon, E
Dim strChar, strDelimited
Dim intLeftComma, intRightComma
Dim Result
Dim fabSplit, ImportStringss
Dim IntCC
Dim strCommentChar 

Result = Rhino.CurrentView ("Top")
Result = Rhino.Command ("_NoEcho")
Result = Rhino.Command ("SetRedrawOff")

Const ForReading = 1
FileName = "Toolpath Files (*.gcode;*.gco)| *.gcode;*.gco|Text Files (*.txt)|*.txt|All Files (*.*)|*.*||"
FileName = Rhino.OpenFileName("Open", FileName)
If IsNull(FileName) Then
Exit Sub
End If

Set FabrixFSO = CreateObject("Scripting.FileSystemObject")
Set oFile = FabrixFSO.OpenTextFile(FileName, ForReading)

intLineTotal = 0

While Not oFile.AtEndOfStream
  strLine = oFile.ReadLine
  intLineTotal = intLineTotal + 1
Wend

oFile.Close
Set oFile = FabrixFSO.OpenTextFile(FileName, ForReading)

ReDim arrXYZ (intLineTotal)

' *** 

arrRhinoUnits (0) = "No unit system"
arrRhinoUnits (1) = "Microns"
arrRhinoUnits (2) = "Millimeters"
arrRhinoUnits (3) = "Centimeters"
arrRhinoUnits (4) = "Meters"
arrRhinoUnits (5) = "Kilometers"
arrRhinoUnits (6) = "Microinches"
arrRhinoUnits (7) = "Mils"
arrRhinoUnits (8) = "Inches"
arrRhinoUnits (9) = "Feet "
arrRhinoUnits (10)= "Miles"

arrItems (0) = "origin x,y,z"  : arrValues (0) = "0,0,0"
arrItems (1) = "units"     : arrValues (1) = arrRhinoUnits(Rhino.UnitSystem)
arrItems (2) = "layer name for path without extusion"      : arrValues (2) = "E-Off(Move)"
arrItems (3) = "RGB Color Param for G0"     : arrValues (3) = "230,230,230"
arrItems (4) = "layer name for path with extusion"      : arrValues (4) = "E-On(Extrude)"
arrItems (5) = "RGB Color Param for G1"     : arrValues (5) = "191,63,63"
arrItems (6) = "comment char in GCODE"       : arrValues (6) = ";"

strMessage = "Edit as appropriate"
strTitle = "Toolpath Properties"

strProperties = Rhino.PropertyListBox (arrItems, arrValues, strMessage, strTitle)
If IsNull(strProperties) Then
  Exit Sub
End If


fabSplit = Split (strProperties(0), ",")
X = Eval (fabSplit (0)) :  Y = Eval (fabSplit (1)) : Z = Eval (fabSplit (2))
arrXYZ (0) = Array (X, Y, Z)


If arrValues(1) <> strProperties (1) Then

strUnitsError = "Error."
  Rhino.MessageBox strUnitsError,,"Fabrix Script"
  Exit Sub
End If


fabSplit = Split (strProperties(3), ",")
If Not Rhino.IsLayer (strProperties(2)) Then
  Rhino.AddLayer strProperties (2), RGB (Eval (fabSplit (0)), Eval (fabSplit (1)), Eval (fabSplit (2)))
End If  



fabSplit = Split (strProperties(5), ",")
If Not Rhino.IsLayer (strProperties(4)) Then
  Rhino.AddLayer strProperties (4), RGB (Eval (fabSplit (0)), Eval (fabSplit (1)), Eval (fabSplit (2)))
End If  


strCommentChar = strProperties(6)

' *** End Properties

intLineCount = 0
strLines = ""

i = 0
G = -1
M = -1

Rhino.print("Start Reading G-Codes. Please Wait.")

While Not oFile.AtEndOfStream                              
  
  strLine = oFile.ReadLine
  intCC = 0
  strDelimited = ""
  If Len (strLine) <> 0 Then                                 
    For L = 1 To Len (strLine)                              
      strChar = Mid (strLine, L, 1)
      Select Case strChar
        Case strCommentChar
          Exit For
        Case " ",","      
        Case "-",".","0","1","2","3","4","5","6","7","8","9"
          strDelimited = strDelimited & strChar
        Case Else
          strDelimited = strDelimited & "," & strChar & ","
      End Select
    Next                                                     

    intLeftComma = Abs(Left (strDelimited, 1) = ",")
    intRightComma = Abs(Right (strDelimited, 1) = ",")
    strDelimited = Mid (strDelimited, 1+ intLeftComma, Len (strDelimited) - intLeftComma - intRightComma)
  
  fabSplit = Split (strDelimited, ",")
  'Rhino.print(strDelimited)
  
	
	
  For L = 0 to UBound (fabSplit)

  	Eon = 0
    ImportStringss = Left (fabSplit (L), 1)

    Select Case ImportStringss

    Case "X", "Y", "Z"

       If (G=0 Or G=1) Then
         intCC = 1
         Execute ImportStringss & "=" & fabSplit (L+1)
       End If	


	Case "E" E = Eval (fabSplit (L+1))
	'Rhino.print(E)
	   If ( E> 0) Then
	    Result = Rhino.CurrentLayer (strProperties (4))
      Else 
        Result = Rhino.CurrentLayer (strProperties (2))
	   End If

    Case "G" G = Eval (fabSplit (L+1))

      If (G=0 Or G=1) Then

      If i > 0 Then
        ReDim Preserve arrXYZ (i)
        Result = Rhino.AddPolyline (arrXYZ)
		Rhino.ObjectName Result, strLine
        ReDim arrXYZ (intLineTotal)
        i = 0
        arrXYZ (i) = Array (X , Y , Z)
      End If

      Else
	  ' G=0 G=1 以外
	   Result = Rhino.AddPoint (arrXYZ(i)) 
       Rhino.ObjectName Result, strLine
	  

      End If

    Case "M" M = Eval (fabSplit (L+1))

      If i > 0 And M = 30 Then
        ReDim Preserve arrXYZ (i)
        Result = Rhino.AddPolyline (arrXYZ)		 
         Rhino.ObjectName Result, strLine	
        ReDim arrXYZ (intLineTotal)
        i = 0
        arrXYZ (i) = Array (X , Y , Z)
      
	  Else 
	    ' M30 以外
	    Result = Rhino.AddPoint (arrXYZ(i))
		Rhino.ObjectName Result,  strLine
	  
	  End If

    End Select

  Next

  End If                                                    
  
  If IntCC = 1 Then
  i = i + 1
  arrXYZ (i) = Array (X , Y , Z)
  End If

  
  If intLineCount < 25 Then
    strLines = strLines & strLine & VbCrLf
  End If

  intLineCount = intLineCount + 1

Wend                                                         

Result = Rhino.Command ("SetRedrawOn")
strLines = strLines & " ... " & VbCrLf & VbCrLf & "of " & CStr (intLineCount) & " lines"
Rhino.MessageBox strLines,,"Fabrix Script G-CODE-IMPORT PLUGIN for Rhino (c) Hiroya Tanaka"

oFile.Close
Set FabrixFSO = Nothing

End Sub
