' 3D-G-CODE SCRIPT

'///////////////////////////////////////////////////////////////////////////////////////////////////////////////////////////////////////////////////////////////////////////////////////////////
'//
'//
'// Fabrix Script
'// G-CODE-EXPORT PLUGIN for Rhino
'// (c) Hiroya Tanaka, Social Fabrication Lab, Keio University, Japan, 2016 - 2017
'// 
'// Project Official Website:  http://www.fabrix.design/ 
'// 
'// 
'///////////////////////////////////////////////////////////////////////////////////////////////////////////////////////////////////////////////////////////////////////////////////////////////


Option Explicit

' global constants
Dim DFLT_SAVE_FN : DFLT_SAVE_FN = "3dgcode.gco"
Dim ERR_LAYER_NAME : ERR_LAYER_NAME = "--Errors in path--"


' global variables
Dim lastG
Dim NC_FILE
Dim ERR_MSG: ERR_MSG = null
Dim SIMPLIFY_CURVES
Dim ALIGN_TO_ORIGIN
Dim SAFE_Z
Dim RAPID_Z
Dim FEED_RATE
Dim EXTRUSION_RATIO
Dim WORK_TOP
Dim APPROACH_TOP
Dim PLUNGE_FEED
Dim CUT_FEED
Dim STEP_DOWN
Dim NO_DOWNSTEPS
Dim CURR_DOWNSTEP
Dim CUT_DEPTH 
CUT_DEPTH = 0
Dim PLUNGE_OFFSET
Dim TOP_PASS
Dim ret
Dim extrude
Dim extrudetwo
Dim head
head = 1
extrude = 0
extrudetwo = 0
Dim heatbed
Dim hotend
Dim hotendtwo
Dim lastx
Dim lasty
Dim lastz
Dim AESM
Dim filament
Dim extwidth
Dim extheight

		

call main ' exec on load

Sub main
	
	SetLocale ("en-us") ' enforces "." as decimal separator

	Dim selectedCurves : selectedCurves = Rhino.getObjects("Select Polyline(s)...", 4, ,true,false) 
	if isNull(selectedCurves) then Exit Sub 
	
	Dim i
	Redim closedCurves(-1)
	Redim openCurves(-1)
	for i=0 to ubound(selectedCurves)
		if Rhino.isCurveClosed(selectedCurves(i)) then
			addEl closedCurves,selectedCurves(i)
		else
			addEl openCurves,selectedCurves(i)
		end if
	next
	
	if ubound(openCurves)>-1 then
		Rhino.selectObjects openCurves
		Rhino.command("_Dir")
	end if
	
	if ubound(closedCurves)>-1 then
		Rhino.selectObjects closedCurves
		Rhino.command("_CrvSeam")
	end if

	Rhino.selectObjects selectedCurves
	
	'Rhino.print("IF WEIRD ARCS TRY WITHOUT SIMPLIFY")
	'Dim params : params = Array( "TopPass", "No", "Yes", "Simplify", "No", "Yes", "AlignToOrigin", "No", "Yes", "Adjust","LastStep","StepDown")
	'Dim paramDflts : paramDflts = Array( false, false, false, false)
	'Dim paramsChosen : paramsChosen = Rhino.getBoolean("Press enter to accept: ", params, paramDflts)
	'If not IsArray(paramsChosen) Then Exit Sub
	



	Rhino.enableRedraw(False)

	Dim preparedCurves : preparedCurves = prepareCurves(selectedCurves) 'make sure all is in order
	

    preparedCurves = sort(preparedCurves)
			
			
	if isNull(ERR_MSG) then

		if inputparams then

		
			

CUT_DEPTH=0
NO_DOWNSTEPS = 0

		


			' setup output file
			Dim fileName : fileName = Rhino.saveFileName("Output file", "G-Code Files (*.gco)|*.gco|All Files (*.*)|*.*|", , DFLT_SAVE_FN)
			if not isNull(fileName) then
				Dim fileSystem
				Set fileSystem = CreateObject("Scripting.FileSystemObject")
				On Error Resume Next
				Set NC_FILE = fileSystem.createTextFile(fileName, true)
				if not Err then
					NC_Init(fileName)
					for i = 0 to ubound(preparedCurves)


Dim arrLineTypes, strLinetype, arrObjects, strObject

arrLinetypes = Rhino.LinetypeNames






If StrComp(Rhino.ObjectLinetype(preparedCurves(i)), arrLinetypes(0), vbBinaryCompare) = 0  Then

  NC_FILE.writeLine()
  NC_FILE.writeLine("; ##### LineType 1 #####")
  NC_FILE.writeLine("T0")
  NC_FILE.writeLine("; #####")
  NC_FILE.writeLine()
head = 1
else 
 NC_FILE.writeLine()
 NC_FILE.writeLine("; ##### LineType 2 #####")
 NC_FILE.writeLine("T1")
 NC_FILE.writeLine("; #####")
 NC_FILE.writeLine()
head = 2
End If 

						processPreparedCurve(preparedCurves(i))
					next
					NC_EndProgram
					NC_FILE.Close()
					NC_FILE = Nothing
				else
					ERR_MSG= Err.Description
				end if
			end if
		end if
	end if
	
	'if not isNull(preparedCurves) then Rhino.deleteObjects(preparedCurves)  'cleanup

	Rhino.UnselectAllObjects


	Rhino.enableRedraw(true)

End Sub


Function inputparams
	inputparams=false	
		FEED_RATE = Rhino.GetReal ("FEED_RATE", 1200)
		if isNull(FEED_RATE) then Exit Function
	
		EXTRUSION_RATIO = Rhino.GetReal ("EXTRUSION_Multiplier", 0.5)
		if isNull(EXTRUSION_RATIO) then Exit Function

		ret = Rhino.GetReal ("Retract (mm)", 2)
		if isNull(ret) then Exit Function

		heatbed = Rhino.GetReal ("heatbed temparature(c)",  55)
		if isNull(heatbed) then Exit Function
	
		hotend = Rhino.GetReal ("hotend one temparature", 195)
		if isNull(hotend) then Exit Function

		hotendtwo = Rhino.GetReal ("hotend two temparature", 160)
		if isNull(hotendtwo) then Exit Function
		
Dim arrItems, arrDefaults, arrResults, blnVal
arrItems = Array( "Mode", "Off", "On")
arrDefaults = array(False)


		AESM = Rhino.GetBoolean ("Advanced Extrusion Setting ",  arrItems, arrDefaults)
	
     if(AESM(0)) then 
	   	filament = Rhino.GetReal ("filament_diameter",  1.75)
		if isNull(filament) then Exit Function 
		
		extwidth = Rhino.GetReal ("printed extrusion width",  0.45)
		if isNull(extwidth) then Exit Function 
		
		extheight = Rhino.GetReal ("printed extrusion height",  0.2)
		if isNull(extheight) then Exit Function 
     end if

	inputparams=true	
end function


'*********************************************************************
'* explode all selected to simple arcs and lines
'* this is to ensure:
'*	counter clockwise order of "selection"
'* 	all curves to be joined into closed/open polycurves
'*	additional processing on sub-curves can be added here
'*********************************************************************
Function prepareCurves(selectedCurves)




		prepareCurves = selectedcurves


End Function




'*********************************************************************
'* explode one polycurve and create gcode for it
'*********************************************************************
Sub processPreparedCurve(curve)





	Dim curveStartPoint : curveStartPoint = Rhino.curveStartPoint(curve)
       '	Dim isOpenCurve : isOpenCurve = not Rhino.isCurveClosed(curve)
         Dim explodedCurve : explodedCurve = Rhino.explodeCurves(curve,false,true)
        NC_PrepareCut(curveStartPoint)
        	Dim i
			For i = 0 To uBound(explodedCurve)-1 
				processSubCurve(explodedCurve(i))
			next
                        processSubCurvelast(explodedCurve(uBound(explodedCurve)))
	
	If uBound(explodedCurve)>1 Then
	Rhino.deleteObjects(explodedCurve)
	end if
	
End Sub




'*********************************************************************
'* create gcode for arc or line
'*********************************************************************
Function processSubCurve(subcurve)

	Dim point : point = Rhino.curveEndPoint(subcurve)


If head = 1 Then
        
       if(AESM(0)) then 
	   
	      extrude= extrude + EXTRUSION_RATIO * distance(NC_NUMBER(point(0)), NC_NUMBER(point(1)), NC_NUMBER(point(2)), lastx, lasty, lastz) * extheight * extwidth / ((Rhino.PI*(filament/2)*(filament/2)))

	   
	   
	   else 
                extrude= extrude + EXTRUSION_RATIO * distance(NC_NUMBER(point(0)), NC_NUMBER(point(1)), NC_NUMBER(point(2)), lastx, lasty, lastz)
            
	   end if
	      	NC_FILE.writeLine ("T0")
                NC_FILE.writeLine()
                NC_FILE.writeLine("; path point T0")
		        NC_FILE.writeLine ("G1 X" & NC_NUMBER(point(0)) & " Y" & NC_NUMBER(point(1)) & " Z" & NC_NUMBER(point(2)) & " E" & extrude & " F" & FEED_RATE)
 
else 

       if(AESM(0)) then 
	   
	      extrude= extrude + EXTRUSION_RATIO * distance(NC_NUMBER(point(0)), NC_NUMBER(point(1)), NC_NUMBER(point(2)), lastx, lasty, lastz) * extheight * extwidth / ((Rhino.PI*(filament/2)*(filament/2)))

	   
	   
	   else   
                extrudetwo= extrudetwo + EXTRUSION_RATIO * distance(NC_NUMBER(point(0)), NC_NUMBER(point(1)), NC_NUMBER(point(2)), lastx, lasty, lastz)
        	
	    end if
		    NC_FILE.writeLine ("T1")
                NC_FILE.writeLine()
                NC_FILE.writeLine("; path point T1")
	         	NC_FILE.writeLine ("G1 X" & NC_NUMBER(point(0)) & " Y" & NC_NUMBER(point(1)) & " Z" & NC_NUMBER(point(2)) & " E" & extrudetwo & " F" & FEED_RATE)

End If

	
End Function

Function processSubCurvelast(subcurve)

	Dim point : point = Rhino.curveEndPoint(subcurve)

If head = 1 Then
        
		 
		 if(AESM(0)) then 
			   extrude= extrude + (EXTRUSION_RATIO * distance(NC_NUMBER(point(0)), NC_NUMBER(point(1)), NC_NUMBER(point(2)), lastx, lasty, lastz) * extheight * extwidth) / ((Rhino.PI*(filament/2)*(filament/2)))
			
          else 
               extrude= extrude + (EXTRUSION_RATIO * distance(NC_NUMBER(point(0)), NC_NUMBER(point(1)), NC_NUMBER(point(2)), lastx, lasty, lastz))
        
          end if
		  
		         	NC_FILE.writeLine ("T0")
                NC_FILE.writeLine()
                NC_FILE.writeLine("; path point T0 last")
		        NC_FILE.writeLine ("G1 X" & NC_NUMBER(point(0)) & " Y" & NC_NUMBER(point(1))& " Z" & NC_NUMBER(point(2)) & " E" & extrude & " F" & FEED_RATE)
		  
		  
else 

		 if(AESM(0)) then 
		   extrude= extrude + (EXTRUSION_RATIO * distance(NC_NUMBER(point(0)), NC_NUMBER(point(1)), NC_NUMBER(point(2)), lastx, lasty, lastz) * extheight * extwidth) / ((Rhino.PI*(filament/2)*(filament/2)))

		 
		 
		 else
               extrudetwo= extrudetwo + (EXTRUSION_RATIO * distance(NC_NUMBER(point(0)), NC_NUMBER(point(1)), NC_NUMBER(point(2)), lastx, lasty, lastz))
          
        end if
		
		  	NC_FILE.writeLine ("T1")
                NC_FILE.writeLine()
                NC_FILE.writeLine("; path point T1 last")
	    	    NC_FILE.writeLine ("G1 X" & NC_NUMBER(point(0)) & " Y" & NC_NUMBER(point(1)) & " Z" & NC_NUMBER(point(2)) & " E" & extrudetwo & " F" & FEED_RATE)
End If

if ret>0 then
  NC_FILE.writeLine()
  NC_FILE.writeLine("; retract at end point")

If head =1 then 
  NC_FILE.writeLine("T0")
  extrude = extrude - ret 

  NC_FILE.writeLine("G1 E" & extrude  & " F1800.00000")

else
  NC_FILE.writeLine("T1")
  extrudetwo = extrudetwo - ret

  NC_FILE.writeLine("G1 E" & extrudetwo & " F1800.00000")

End If
End If


End Function


'*********************************************************************
'* sort curves
'*********************************************************************
Function sort(arr)
	if ubound(arr)=0 then 
		sort = arr
		exit function
	end if
	Dim fo : fo = Rhino.getObject("press enter to use z-ordering polyline", 4, false, false, arr)
	Dim i,j,pt1,pt2,md,d,mp

'	if isNull(fo) then
'		'find the leftmost lowest curve
'		md=null
'		for i=0 to ubound(arr)
'			pt1=Rhino.curveStartPoint(arr(i))
'			d=pt1(2)
'			if isNull(md) then
'				md=d
'				mp=i
'			elseif d<md then
'				md=d
'				mp=i
'			elseif d=md then
'				pt2=Rhino.curveStartPoint(arr(mp))
'				if pt1(2)<pt2(2) then
'					md=d
'					mp=i
'				end if
'			end if
'		next
'	else
'		for i=0 to ubound(arr)
'			if fo=arr(i) then
'				mp=i
'			end if
'		next 
'	end if
'	pt1=arr(0)
'	arr(0)=arr(mp)
'	arr(mp)=pt1


if isNull(fo) then
		Rhino.print("Sorting... would take time, Please wait.")
	'sort
	for i=1 to ubound(arr)

		pt1=Rhino.curveEndPoint(arr(i-1))
	    ' md = minimum z 
		md=pt1(2)
		for j=i to ubound(arr)
			pt2=Rhino.curveStartPoint(arr(j))

				if md>pt2(2) then
				md=pt2(2)
				mp=j
			end if
		next
		
		if pt1(2)>md then
		'Rhino.print("exchange")
		pt2=arr(i-1)
		arr(i-1)=arr(mp)
		arr(mp)=pt2
		end if 
		
	next
	sort=arr
	

end If	
	
End Function



'*********************************************************************
'* gcode
'*********************************************************************
Sub NC_Init(fileName)
	NC_FILE.writeLine(";// Fabrix Script")
    NC_FILE.writeLine(";// G-CODE-IMPORT PLUGIN for Rhino")
	NC_FILE.writeLine(";// c) Hiroya Tanaka, Social Fabrication Lab, Keio University, Japan, 2016 - 2017")
	NC_FILE.writeLine(";			// Project Official Website:  http://www.fabrix.design/ ")



	NC_FILE.writeLine(";(" & fileName & ")")

NC_FILE.writeLine("")
NC_FILE.writeLine(";=============================")
NC_FILE.writeLine("; Standard Header Start")
NC_FILE.writeLine("M107")
NC_FILE.writeLine("M190 S" & heatbed)
NC_FILE.writeLine("M104 S" & hotend & " T0")
NC_FILE.writeLine("M104 S" & hotendtwo & " T1")
NC_FILE.writeLine("M891 P0")
NC_FILE.writeLine("T0")
NC_FILE.writeLine("G28")
NC_FILE.writeLine("G90")
NC_FILE.writeLine("G1 Z5 F5000")
NC_FILE.writeLine("M109 S" & hotend & " T0")
NC_FILE.writeLine("M109 S" & hotendtwo & " T1")
NC_FILE.writeLine("G1 X10 Y10")
NC_FILE.writeLine("G21") 
NC_FILE.writeLine("G90") 
NC_FILE.writeLine("M82")

NC_FILE.writeLine("T0")
NC_FILE.writeLine("G92 E0")

if ret>0 then 

  NC_FILE.writeLine("; extract [-R] at [beginning] point")

  extrude = extrude - ret 
  NC_FILE.writeLine("G1 E" & extrude & " F1800.00000")
end if


NC_FILE.writeLine("T1")

NC_FILE.writeLine("G92 E0")
if ret>0 then 

  extrudetwo = extrudetwo - ret 
  NC_FILE.writeLine("G1 E" & extrudetwo & " F1800.00000")
end if

NC_FILE.writeLine("M106")
NC_FILE.writeLine("; M106 Fan On")
NC_FILE.writeLine("; Standard Header End")
NC_FILE.writeLine(";=============================")
NC_FILE.writeLine("")


End Sub

Sub NC_EndProgram

NC_FILE.writeLine("")
NC_FILE.writeLine(";=============================")
NC_FILE.writeLine ("; Standard Footer Start")
NC_FILE.writeLine ("M107")
NC_FILE.writeLine ("M400")
NC_FILE.writeLine ("M104 S0 T0")
NC_FILE.writeLine ("M104 S0 T1")
NC_FILE.writeLine ("M140 S0")
NC_FILE.writeLine ("G1 Y300 F6000")
NC_FILE.writeLine ("T0")
NC_FILE.writeLine ("G28 X")
NC_FILE.writeLine ("G91")
NC_FILE.writeLine ("G1 Z100 F600")
NC_FILE.writeLine ("G90")
NC_FILE.writeLine ("M701")
NC_FILE.writeLine ("M107")
NC_FILE.writeLine ("; M107 Fan Off")
NC_FILE.writeLine ("M84")
NC_FILE.writeLine ("; Standard Footer End")
NC_FILE.writeLine(";=============================")
NC_FILE.writeLine("")

End Sub

Sub NC_PrepareCut(point)


	NC_FILE.writeLine (";...set new start point...")
	NC_FILE.writeLine ("G0 X" & NC_NUMBER(point(0)) & " Y" & NC_NUMBER(point(1)) & " Z" & NC_NUMBER(point(2)))
        lastx= NC_NUMBER(point(0))
        lasty= NC_NUMBER(point(1))
        lastz= NC_NUMBER(point(2))

if ret>0 then
  NC_FILE.writeLine()
  NC_FILE.writeLine("; extract [+R] at [start] point")

  NC_FILE.writeLine("T0")
  extrude = extrude + ret 
  NC_FILE.writeLine("G1 E" & extrude &" F1800.00000")

  NC_FILE.writeLine("T1")
  extrudetwo = extrudetwo + ret 
  NC_FILE.writeLine("G1 E" & extrudetwo &" F1800.00000")

end if




End Sub

Sub NC_StepDown
'	NC_FILE.writeLine ("F" & PLUNGE_FEED)
'	if CURR_DOWNSTEP=NO_DOWNSTEPS then
'		NC_FILE.writeLine ("G1 Z" & NC_NUMBER((WORK_TOP-CUT_DEPTH)) & " (...step " & CURR_DOWNSTEP & "/" & NO_DOWNSTEPS & " enter strategy...)")
'	else
'		NC_FILE.writeLine ("G1 Z" & NC_NUMBER((WORK_TOP-CURR_DOWNSTEP*STEP_DOWN)) & " (step " & CURR_DOWNSTEP & "/" & NO_DOWNSTEPS & " enter strategy...)")
'	end if
'	NC_FILE.writeLine ("F" & CUT_FEED)
	lastG = "G1"
End Sub

Sub NC_EndCut 



	lastG = "G0"
End Sub


'*********************************************************************
'* helpers
'*********************************************************************

Function NC_NUMBER(val)
	'NC_NUMBER = round(val,4)
NC_NUMBER = val
End Function

Function addEl (array, el) ' simple dynamic array
	Dim i : i = ubound(array)+1
	Redim Preserve array(i)
	array(i)=el
	addEl=i
End Function


Function distance(x,y,z,xx,yy,zz) 
distance = Sqr((xx-x)*(xx-x) + (yy-y)*(yy-y) + (zz-z)*(zz-z) )
End Function
